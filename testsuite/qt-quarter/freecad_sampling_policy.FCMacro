# Real FreeCAD viewer and screen-content contracts, with explicit per-view policy.
from pathlib import Path
import os
exec((Path(os.environ['COIN_TEST_MACRO_DIR']) / 'freecad_screen_content.FCMacro').read_text())
report['test'] = 'freecad-sampling-policy'
policy = int(os.environ.get('COIN_TEST_PORTABLE_SAMPLING', '1'))
report['sampling_policy'] = policy
cold_border_qualify = os.environ.get('COIN_TEST_COLD_BORDER_QUALIFY') == '1'
original_axes_baseline = axes_baseline
original_capture = capture

# This automated content fixture drives camera and picking through the API.
# Discard interactive input in this private host process so a cursor gesture or
# toolbar shortcut cannot mutate its camera/document between screen captures.
class SamplingFixtureInputGuard(QtCore.QObject):
    blocked = {QtCore.QEvent.MouseButtonPress, QtCore.QEvent.MouseButtonRelease,
               QtCore.QEvent.MouseButtonDblClick, QtCore.QEvent.MouseMove,
               QtCore.QEvent.Wheel, QtCore.QEvent.KeyPress, QtCore.QEvent.KeyRelease,
               QtCore.QEvent.ContextMenu, QtCore.QEvent.TouchBegin,
               QtCore.QEvent.TouchUpdate, QtCore.QEvent.TouchEnd,
               QtCore.QEvent.NativeGesture}
    def eventFilter(self, obj, event):
        if event.type() in self.blocked:
            report['interactive_input_blocked'] = report.get('interactive_input_blocked', 0) + 1
            return True
        return False

sampling_input_guard = SamplingFixtureInputGuard()
QtWidgets.QApplication.instance().installEventFilter(sampling_input_guard)
report['fixture_interactive_input'] = 'blocked in this host process'

def axes_baseline():
    widget = viewer_widget()
    main = Gui.getMainWindow()
    # EWMH changes stacking without recreating Qt's native surface.
    import subprocess
    subprocess.run(['wmctrl', '-i', '-r', hex(int(main.winId())), '-b',
                    'add,above'], check=True, timeout=3)
    loop = QtCore.QEventLoop()
    QtCore.QTimer.singleShot(60, loop.quit)
    loop.exec()
    state = subprocess.check_output(['xprop', '-id', hex(int(main.winId())),
                                     '_NET_WM_STATE'], timeout=3).decode()
    if '_NET_WM_STATE_ABOVE' not in state:
        raise RuntimeError('window manager did not admit ABOVE for the test host')
    report['fixture_window_state'] = state.strip()
    main.raise_()
    main.activateWindow()
    report['fixture_window_stays_on_top'] = True
    widget.setFocus()
    widget.setProperty('coinRenderPortableSampling', bool(policy))
    # Establish the same top camera before adapter recreation's first baseline.
    # The cold-border qualification observes its first presented result without
    # the two host redraws used by the steady profile.
    view.viewTop()
    if not cold_border_qualify:
        for _ in range(2):
            view.redraw()
            Gui.updateGui()
    report['prebaseline_redraws'] = 0 if cold_border_qualify else 2
    original_axes_baseline()
    # Exercise filter=2 in the real host as well as legacy raster content:
    # a 256-square texture on this small face reaches mip minification at DPR1
    # and under the existing projective mutation at DPR2.
    for name, switch, node, anchor in stages:
        if name != 'projective-uv':
            continue
        group = switch.getChild(0)
        pattern = bytes(channel for y in range(256) for x in range(256)
                        for channel in ((255,255,0,255) if ((x//16+y//16)%2)
                                        else (0,128,255,255)))
        for index in range(group.getNumChildren()):
            child = group.getChild(index)
            if child.isOfType(coin.SoTexture2.getClassTypeId()):
                child.image.setValue(coin.SbVec2s(256,256),4,pattern)
            if child.isOfType(coin.SoComplexity.getClassTypeId()):
                child.textureQuality = .5
        report['projective_sampling_fixture'] = {'dimensions':[256,256],
            'quality':.5,'filter':'NEAREST_MIPMAP_LINEAR','unit':0}

def capture(name):
    widget = viewer_widget()
    Gui.getMainWindow().raise_()
    # Dismiss only this test host's menus/tooltips, which otherwise occlude
    # screen pixels and invalidate comparison with its bare viewport.
    popup = QtWidgets.QApplication.activePopupWidget()
    if popup is not None:
        popup.close()
        report['dismissed_popups'] = report.get('dismissed_popups', 0) + 1
    QtWidgets.QToolTip.hideText()
    # The first cold baseline observes the presented viewport before any
    # fixture-forced redraw. Later captures retain the steady-host fence.
    first_cold = cold_border_qualify and name == 'cold-before'
    if not first_cold:
        view.redraw()
        Gui.updateGui()
    active = widget.property('coinRenderActiveSamplingPolicy')
    if native and (active is None or int(active) != policy):
        raise RuntimeError('explicit sampling policy was not admitted by the real host')
    report['active_sampling_policy'] = int(active) if active is not None else None
    # Qt redraw return does not fence the desktop compositor. Require two
    # identical screen reads after event processing, with a bounded deadline.
    # This waits for presentation; it does not change any image/removal gate.
    deadline = time.monotonic() + 0.5
    previous = None
    attempt = 0
    while time.monotonic() < deadline:
        if not first_cold:
            view.redraw()
        Gui.updateGui()
        loop = QtCore.QEventLoop()
        QtCore.QTimer.singleShot(60, loop.quit)
        loop.exec()
        image = original_capture(name)
        attempt += 1
        if previous is not None and image == previous:
            report.setdefault('presentation_reads', {})[name] = attempt
            if first_cold:
                report['cold_baseline_no_forced_redraw'] = True
                report['cold_baseline_frame_count'] = int(widget.property('wgpuFrameCount') or 0)
            return image
        if previous is not None:
            previous.save(str(artifacts / (name + '-presentation-' + str(attempt-1) + '.png')))
        previous = image
    raise RuntimeError('screen presentation did not settle within 0.5s: ' + name)

# Bound queued cleanup work before measuring idle. The final 1.2s idle gate
# remains exact; a perpetual frame loop never reaches this baseline.
import time
idle_deadline = None
idle_last = None
idle_stable_since = None
original_idle_baseline = content_idle_baseline

def content_idle_baseline():
    global idle_deadline, idle_last, idle_stable_since
    now = time.monotonic()
    count = int(viewer_widget().property('wgpuFrameCount') or 0)
    if idle_deadline is None:
        idle_deadline = now + 5.0
        idle_last = count
        idle_stable_since = now
    if count != idle_last:
        idle_last = count
        idle_stable_since = now
    if now - idle_stable_since >= 0.6:
        report['idle_cleanup_settle_s'] = 5.0 - (idle_deadline-now)
        original_idle_baseline()
    elif now >= idle_deadline:
        raise RuntimeError('cleanup did not settle within 5s')
    else:
        step(content_idle_baseline, 100)

# Qualify steady host integration after first-use font/raster resources exist.
# The separate cold-start diagnostic remains open; do not infer its correctness
# from this warmed profile. All subsequent image/removal gates are unchanged.
original_sampling_baseline_ready = baseline_ready

def baseline_ready():
    if cold_border_qualify:
        report['qualification_scope'] = 'first document border before text warmup'
        before = capture('cold-before')
        text_switch, text_node = stages[0][1:3]
        text_switch.whichChild = coin.SO_SWITCH_ALL
        visible = capture('cold-text-visible')
        text_node.string.setValues(0, ['Updated P03'])
        updated = capture('cold-after-text-mutation')
        text_switch.whichChild = coin.SO_SWITCH_NONE
        after = capture('cold-after-hide')
        repeated = capture('cold-after-hide-repeat')
        rect = QtCore.QRect(0,0,before.width()-1,before.height()-1)
        report['cold_text_visible_changes'] = changes(before, visible, rect)
        report['cold_text_mutation_changes'] = changes(visible, updated, rect)
        report['cold_border_after_hide_changes'] = changes(before, after, rect)
        report['cold_border_repeat_changes'] = changes(after, repeated, rect)
        if not report.get('cold_baseline_no_forced_redraw') or report['cold_baseline_frame_count'] <= 0:
            raise RuntimeError('first cold baseline did not observe a submitted native frame')
        if report['cold_text_visible_changes'] < 100 or report['cold_text_mutation_changes'] < 50:
            raise RuntimeError('cold border control did not exercise visible text and mutation')
        if report['cold_border_after_hide_changes'] > 30 or report['cold_border_repeat_changes'] != 0:
            raise RuntimeError('cold document border changed after text removal')
        report['cold_start_qualified'] = True
        finish()
        return
    diagnostic = os.environ.get('COIN_TEST_COLD_BORDER_DIAGNOSTIC')
    if diagnostic:
        if diagnostic not in ('visible-no-mutation', 'hidden-mutation',
                              'visible-mutation', 'hidden-image-mutation'):
            raise RuntimeError('invalid cold border diagnostic')
        report['cold_border_diagnostic'] = diagnostic
        report['qualification_scope'] = 'cold border diagnostic only'
        report['cold_start_qualified'] = False
        capture('cold-before')
        text_switch, text_node = stages[0][1:3]
        if diagnostic in ('visible-no-mutation', 'visible-mutation'):
            text_switch.whichChild = coin.SO_SWITCH_ALL
            capture('cold-text-visible')
        if diagnostic in ('hidden-mutation', 'visible-mutation'):
            text_node.string.setValues(0, ['Updated P03'])
            capture('cold-after-text-mutation')
        elif diagnostic == 'hidden-image-mutation':
            image_node = stages[1][2]
            image_node.image.setValue(coin.SbVec2s(24,16), 4,
                                      bytes([255,128,0,255] * (24*16)))
            capture('cold-after-image-mutation')
        if diagnostic in ('visible-no-mutation', 'visible-mutation'):
            text_switch.whichChild = coin.SO_SWITCH_NONE
            capture('cold-after-hide')
        finish()
        return
    before = capture('sampling-startup-before-text')
    stages[0][1].whichChild = coin.SO_SWITCH_ALL
    capture('sampling-startup-text-warmup')
    stages[0][1].whichChild = coin.SO_SWITCH_NONE
    after = capture('sampling-startup-after-text')
    rect = QtCore.QRect(0,0,before.width()-1,before.height()-1)
    report['startup_root_changes'] = changes(before,after,rect)
    report['qualification_scope'] = 'steady host after text resource warmup'
    report['cold_start_qualified'] = False
    original_sampling_baseline_ready()
