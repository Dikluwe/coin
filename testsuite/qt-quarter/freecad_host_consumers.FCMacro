# Executed by freecad_screen_content.FCMacro only when explicitly requested.
# Each process exercises one real document consumer, starting without a GL frame.
import ctypes
import sys
import subprocess
import re
import time
sys.dont_write_bytecode = True
sys.path.insert(0, os.environ['COIN_TEST_MACRO_DIR'])
from host_consumer_oracles import (CONSUMERS, LABEL_CONSUMERS, require_content,
                                  require_mutation, require_cleanup,
                                  require_pointer_identity, require_drag,
                                  require_idle, require_dpr, require_interactive_mesh,
                                  require_single_coin, require_host_hover, require_host_selection,
                                  canonical_topology_identity, require_released_draggers,
                                  NativePublicationQuietWindow)
from shiboken6 import isValid, getCppPointer

consumer_name = os.environ['COIN_TEST_HOST_CONSUMER']
if consumer_name not in CONSUMERS:
    raise RuntimeError('unknown host consumer: ' + consumer_name)
if os.environ.get('COIN_TEST_ISOLATED_X11') != '1':
    raise RuntimeError('host consumer input requires run_isolated.py')
report.update(test='freecad-host-consumer', consumer=consumer_name,
              profile=consumer_name, scope='one document consumer', stages=[])
# Private per-process UI profile: an overlaid Tasks dock can both cover pixels
# and intercept native mouse motion. Keep document consumers in a clear viewport.
for overlay_name in ('OverlayLeft', 'OverlayRight', 'OverlayTop', 'OverlayBottom'):
    overlay_group = App.ParamGet('User parameter:BaseApp/MainWindow/DockWindows/' + overlay_name)
    overlay_group.SetString('Widgets', '')
    overlay_group.SetBool('TaskShow', False)
    overlay_group.SetBool('EditShow', False)
report['private_ui_profile'] = {'overlay_widgets': [], 'TaskShow': False, 'EditShow': False}
failure_finish = finish
drag_probe = None
event_callbacks = []


def finish(error=None):
    if error is not None:
        failure_finish(error)
        return
    try:
        global drag_probe
        if drag_probe:
            host_helper.host_consumer_drag_probe_destroy(drag_probe)
            drag_probe = None
        if 'input_observer' in globals():
            input_observer.close()
        if 'view' in globals():
            for event_type, callback in event_callbacks:
                view.removeEventCallback(event_type, callback)
            event_callbacks.clear()
        Gui.Selection.clearSelection()
        if Gui.activeDocument() and Gui.activeDocument().getInEdit():
            Gui.activeDocument().resetEdit()
        documents = list(App.listDocuments().values())
        if not documents:
            raise RuntimeError('host teardown has no document to save')
        for document in documents:
            document.recompute()
            document.saveAs(str(artifacts / (document.Name + '.FCStd')))
        for document in documents:
            App.closeDocument(document.Name)
        if App.listDocuments():
            raise RuntimeError('host teardown left an open document')
        x11.XCloseDisplay(display)
        report.update(status='PASS' if native else 'REFERENCE_PASS',
                      shutdown={'mode': 'normal-host-close', 'saved_documents': len(documents),
                                'documents_closed': True, 'probes_removed': True,
                                'filters_removed': True})
        (artifacts / 'result.json').write_text(json.dumps(report, indent=2))
        os.write(1, ('RESULT ' + json.dumps(report) + '\n').encode())
        def close_host():
            if not Gui.getMainWindow().close():
                failure_finish(RuntimeError('FreeCAD refused normal main-window close'))
        QtCore.QTimer.singleShot(0, close_host)
    except Exception as error:
        failure_finish(error)


try:
    report['coin_images'] = require_single_coin(Path('/proc/self/maps').read_text())
except Exception as error:
    finish(error)
x11 = ctypes.CDLL('libX11.so.6')
xtst = ctypes.CDLL('libXtst.so.6')
x11.XOpenDisplay.argtypes = [ctypes.c_char_p]
x11.XOpenDisplay.restype = ctypes.c_void_p
x11.XFlush.argtypes = [ctypes.c_void_p]
x11.XCloseDisplay.argtypes = [ctypes.c_void_p]
xtst.XTestFakeMotionEvent.argtypes = [ctypes.c_void_p, ctypes.c_int, ctypes.c_int,
                                    ctypes.c_int, ctypes.c_ulong]
xtst.XTestFakeButtonEvent.argtypes = [ctypes.c_void_p, ctypes.c_uint, ctypes.c_int,
                                    ctypes.c_ulong]
display = x11.XOpenDisplay(os.environ['DISPLAY'].encode())
if not display:
    raise RuntimeError('cannot open private X11 display')
if consumer_name in CONSUMERS:
    host_helper = ctypes.CDLL(os.environ['COIN_TEST_HOST_HELPER'])
    host_helper.host_consumer_drag_probe_create.argtypes = [ctypes.c_void_p]
    host_helper.host_consumer_drag_probe_create.restype = ctypes.c_void_p
    host_helper.host_consumer_drag_probe_count.argtypes = [ctypes.c_void_p, ctypes.c_int]
    host_helper.host_consumer_drag_probe_count.restype = ctypes.c_uint64
    host_helper.host_consumer_drag_probe_destroy.argtypes = [ctypes.c_void_p]
    host_helper.host_consumer_drag_probe_destroy.restype = None
    host_helper.host_consumer_colorbar_set_range.argtypes = [ctypes.c_void_p, ctypes.c_float,
                                                          ctypes.c_float, ctypes.c_int]
    host_helper.host_consumer_colorbar_set_range.restype = ctypes.c_int
    report['coin_images'] = require_single_coin(Path('/proc/self/maps').read_text())


host_helper.host_consumer_input_probe_create.argtypes = [ctypes.c_void_p, ctypes.c_int]
host_helper.host_consumer_input_probe_create.restype = ctypes.c_void_p
host_helper.host_consumer_input_probe_count.argtypes = [ctypes.c_void_p, ctypes.c_int, ctypes.c_int]
host_helper.host_consumer_input_probe_count.restype = ctypes.c_uint64
host_helper.host_consumer_input_probe_motion.argtypes = [ctypes.c_void_p, ctypes.c_int]
host_helper.host_consumer_input_probe_motion.restype = ctypes.c_double
host_helper.host_consumer_input_probe_event.argtypes = [ctypes.c_void_p, ctypes.c_int, ctypes.c_int]
host_helper.host_consumer_input_probe_event.restype = ctypes.c_double
host_helper.host_consumer_input_probe_object.argtypes = [ctypes.c_void_p, ctypes.c_int]
host_helper.host_consumer_input_probe_object.restype = ctypes.c_size_t
host_helper.host_consumer_input_probe_coin_state.argtypes = [ctypes.c_void_p]
host_helper.host_consumer_input_probe_coin_state.restype = ctypes.c_char_p
host_helper.host_consumer_input_probe_publication.argtypes = [ctypes.c_void_p]
host_helper.host_consumer_input_probe_publication.restype = ctypes.c_char_p
host_helper.host_consumer_input_probe_destroy.argtypes = [ctypes.c_void_p]
host_helper.host_consumer_input_probe_destroy.restype = None
host_helper.host_consumer_prepare_edit_ui.argtypes = [ctypes.c_void_p]
host_helper.host_consumer_prepare_edit_ui.restype = ctypes.c_char_p


class NativeInputObserver:
    def __init__(self, viewer):
        # Qt dispatch never enters Python/PySide. Sampling occurs only between
        # input stages, through this C interface to the real QGraphicsView.
        self.pointer = host_helper.host_consumer_input_probe_create(
            getCppPointer(viewer)[0], int(consumer_name == 'mesh-interactive'))
        if not self.pointer:
            raise RuntimeError('cannot observe the real QGraphicsView input')

    def counts(self, kind):
        return {phase: int(host_helper.host_consumer_input_probe_count(self.pointer,index,kind))
                for index,phase in enumerate(('motion','press','release'))}

    @property
    def events(self):
        return self.counts(0)

    @property
    def spontaneous(self):
        return self.counts(1)

    @property
    def seen(self):
        return self.counts(2)

    @property
    def rejected(self):
        return self.counts(3)

    @property
    def last_motion(self):
        values = [host_helper.host_consumer_input_probe_motion(self.pointer,index) for index in range(5)]
        return {'local': values[:2], 'global': values[2:4], 'buttons': int(values[4]),
                'observer': 'C++ Qt eventFilter'}

    @property
    def filter_observations(self):
        return [{'observer': 'C++ Qt eventFilter',
                 **{name: int(host_helper.host_consumer_input_probe_object(self.pointer,index))
                    for index,name in enumerate(('watched_cpp','viewer_cpp','viewport_cpp'))}}]

    def close(self):
        if self.pointer:
            host_helper.host_consumer_input_probe_destroy(self.pointer)
            self.pointer = None

    def coin_state(self):
        return json.loads(host_helper.host_consumer_input_probe_coin_state(self.pointer).decode())

    def last_events(self):
        result = {}
        for phase,name in enumerate(('motion','press','release')):
            values = [host_helper.host_consumer_input_probe_event(self.pointer,phase,index)
                      for index in range(7)]
            result[name] = {'local': values[:2], 'global': values[2:4],
                            'buttons': int(values[4]), 'button': int(values[5]),
                            'timestamp_ms': int(values[6]),
                            'count': self.events[name]}
        return result

    def publication(self):
        state = json.loads(host_helper.host_consumer_input_probe_publication(self.pointer).decode())
        for key in ('frames', 'serial'):
            if key in state:
                state[key] = int(state[key])
        return state


def observe_coin_event_state(stage):
    state = input_observer.coin_state()
    report.setdefault('coin_event_states', []).append(
        {'stage': stage, 'round': round_index, 'qt_last_events': input_observer.last_events(), **state})
    # These snapshots are all taken with no pointer button held, including
    # after the real drag release. Do not repair a stuck state in the fixture.
    if consumer_name in ('measure-distance', 'transform-dragger'):
        require_released_draggers(state)


def active():
    output = subprocess.check_output(['xprop', '-root', '_NET_ACTIVE_WINDOW'],
                                     text=True, timeout=2)
    match = re.search(r'0x[0-9a-fA-F]+', output)
    if not match or int(match.group(), 16) != int(Gui.getMainWindow().winId()):
        raise RuntimeError('FreeCAD lost private X11 focus')


def move(point):
    active()
    viewport = viewer_widget().viewport()
    p = viewport.mapToGlobal(point)
    ratio = viewport.devicePixelRatioF()
    if not xtst.XTestFakeMotionEvent(display, -1, round(p.x()*ratio),
                                    round(p.y()*ratio), 0):
        raise RuntimeError('native motion failed')
    x11.XFlush(display)


def button(pressed, number=1):
    active()
    if not xtst.XTestFakeButtonEvent(display, number, int(pressed), 0):
        raise RuntimeError('native button failed')
    x11.XFlush(display)


def difference(a, b):
    return changes(a, b, QtCore.QRect(0, 0, a.width()-1, a.height()-1))


def optional_ui_observation(function):
    # UI queries can synchronously rebuild a dock hierarchy. Diagnostics must
    # record a deleted wrapper without becoming a substitute for a test gate.
    try:
        return function()
    except RuntimeError as error:
        return {'unavailable_ui_observation': str(error)}


def widget_description(widget):
    return optional_ui_observation(lambda: describe_live_widget(widget))


def describe_live_widget(widget):
    if widget is None or not isValid(widget):
        return None
    parent = widget.parentWidget()
    parent_class = str(parent.metaObject().className()) if parent and isValid(parent) else None
    origin = widget.mapToGlobal(QtCore.QPoint())
    return {'class': str(widget.metaObject().className()), 'name': widget.objectName(),
            'global_rect': [origin.x(),origin.y(),widget.width(),widget.height()],
            'text': widget.text()[:160] if hasattr(widget, 'text') else None,
            'parent_class': parent_class}


def graphics_item_description(item):
    return optional_ui_observation(lambda: describe_live_graphics_item(item))


def describe_live_graphics_item(item):
    if item is None or not isValid(item):
        return None
    rect = item.sceneBoundingRect()
    return {'type': item.type(), 'python_class': type(item).__name__,
            'rect': [rect.x(),rect.y(),rect.width(),rect.height()],
            'widget': widget_description(item.widget()) if hasattr(item, 'widget') else None}


def pointer_ui_state(point):
    return optional_ui_observation(lambda: describe_pointer_ui_state(point))


def describe_pointer_ui_state(point):
    viewer = viewer_widget()
    viewport = viewer.viewport()
    # Capture initial viewport metadata before widgetAt/description calls that
    # can destroy other Qt-owned wrappers as a side effect of layout refresh.
    state = {'viewport_mouse_tracking': optional_ui_observation(lambda: viewport.hasMouseTracking()),
             'viewport': widget_description(viewport)}
    queries = {
        'widget_at': lambda: widget_description(QtWidgets.QApplication.widgetAt(
            viewer_widget().viewport().mapToGlobal(point))),
        'mouse_grabber': lambda: widget_description(QtWidgets.QWidget.mouseGrabber()),
        'focus_widget': lambda: widget_description(QtWidgets.QApplication.focusWidget()),
        'graphics_mouse_grabber': lambda: graphics_item_description(viewer_widget().scene().mouseGrabberItem()),
        'graphics_item_at': lambda: graphics_item_description(viewer_widget().itemAt(point)),
        'graphics_items': lambda: [graphics_item_description(item) for item in viewer_widget().scene().items()]}
    state.update({key: optional_ui_observation(query) for key,query in queries.items()})
    return state


def prepare_mesh_ui():
    if consumer_name != 'mesh-interactive':
        return
    for dock in Gui.getMainWindow().findChildren(QtWidgets.QDockWidget):
        if isValid(dock):
            dock.hide()
    QtWidgets.QToolTip.hideText()
    hidden = []
    for widget in QtWidgets.QApplication.topLevelWidgets():
        if isValid(widget) and widget.isVisible() and widget.windowType() == QtCore.Qt.ToolTip:
            hidden.append(widget_description(widget))
            widget.hide()
    report.setdefault('mesh_hidden_ui_tooltips', []).extend(hidden)


def prepare_edit_ui():
    if not edit_consumer:
        return
    # Use Qt's C++ types: a Python binding's QDockWidget metaobject can miss
    # the actual host docks, just as viewport wrappers can be invalidated.
    authored = json.loads(host_helper.host_consumer_prepare_edit_ui(
        getCppPointer(Gui.getMainWindow())[0]).decode())
    report['private_ui_profile'].setdefault('floating_hidden_edit_docks', []).append(authored)
    if not authored['main_window_present'] or authored['dock_count'] == 0:
        raise RuntimeError('private edit layout found no real host QDockWidgets')
    if any(dock['alive'] and (not dock['floating'] or dock['visible']) for dock in authored['docks']):
        raise RuntimeError('private edit layout did not float and hide its real docks')
    Gui.getMainWindow().raise_()
    Gui.getMainWindow().activateWindow()


def find_nodes(type_name):
    node_type = coin.SoType.fromName(type_name)
    if node_type.isBad():
        raise RuntimeError('required real node is not registered: ' + type_name)
    roots = [view.getViewer().getSoRenderManager().getSceneGraph()]
    # The real viewer owns color bars under a separate named foreground root;
    # it is intentionally absent from the ordinary manager scene graph.
    foreground = coin.SoNode.getByName('foregroundroot')
    if foreground is not None:
        roots.append(foreground)
    found = {}
    for root in roots:
        search = coin.SoSearchAction()
        search.setType(node_type, True)
        search.setInterest(coin.SoSearchAction.ALL)
        search.setSearchingAll(True)
        search.apply(root)
        paths = search.getPaths()
        size = paths.getLength() if hasattr(paths, 'getLength') else len(paths)
        for index in range(size):
            node = paths[index].getTail()
            found[node.getNodeId()] = node
    return list(found.values())


def axes_baseline():
    global target, source, mutate_consumer, expected_nodes, edit_consumer
    global round_index, motion_events, button_events, input_observer
    motion_events, button_events = [], []
    event_callbacks.append(('SoLocation2Event', view.addEventCallback(
        'SoLocation2Event', lambda e: motion_events.append(e))))
    event_callbacks.append(('SoMouseButtonEvent', view.addEventCallback(
        'SoMouseButtonEvent', lambda e: button_events.append(e))))
    input_observer = NativeInputObserver(viewer_widget())
    Gui.getMainWindow().raise_()
    Gui.getMainWindow().activateWindow()
    doc.removeObject('Box')
    source = None
    edit_consumer = False
    expected_nodes = []
    V = App.Vector
    if consumer_name == 'sketcher-datum':
        import Sketcher
        import SketcherGui
        Gui.activateWorkbench('SketcherWorkbench')
        target = doc.addObject('Sketcher::SketchObject', 'Consumer')
        target.addGeometry(Part.LineSegment(V(-5, 0, 0), V(5, 0, 0)), False)
        target.addConstraint(Sketcher.Constraint('Distance', 0, 10.0))
        target.setLabelDistance(0, 4.0)
        expected_nodes = ['SoDatumLabel']
        edit_consumer = True
        def mutate_consumer():
            target.setDatum(0, App.Units.Quantity('14 mm' if round_index == 0 else '8 mm'))
    elif consumer_name == 'measure-distance':
        import Measure
        import MeasureGui
        source = doc.addObject('Part::Feature', 'MeasurementEdge')
        source.Shape = Part.makePolygon([V(-5, 0, 0), V(5, 0, 0), V(9, 0, 0)])
        target = doc.addObject('Measure::MeasureDistance', 'Consumer')
        target.Element1 = (source, ['Vertex1'])
        target.Element2 = (source, ['Vertex2'])
        target.ViewObject.TextColor = (1.0, 1.0, 0.0)
        target.ViewObject.LabelPosition = V(0, 4, 0)
        expected_nodes = ['SoFrameLabel']
        def mutate_consumer():
            # The fixed three-vertex source stays identical in bare/cleanup.
            # Changing the measured endpoint authors a new distance and label.
            target.Element2 = (source, ['Vertex3' if round_index == 0 else 'Vertex2'])
    elif consumer_name in ('mesh-curvature', 'mesh-interactive'):
        import Mesh
        import MeshGui
        if consumer_name == 'mesh-interactive':
            App.ParamGet('User parameter:BaseApp/Preferences/View').SetBool('UseVBO', False)
            App.ParamGet('User parameter:BaseApp/Preferences/Mod/Mesh').SetInt('RenderTriangleLimit', 1)
            report['mesh_authored_preferences'] = {'UseVBO': False, 'RenderTriangleLimit': 1}
            target = doc.addObject('Mesh::Feature', 'Consumer')
            target.Mesh = Mesh.createSphere(5, 16)
            target.ViewObject.ShapeColor = (1.0, .05, .02)
            material = target.ViewObject.ShapeAppearance[0]
            material.SpecularColor = (0.0, 0.0, 0.0)
            material.Shininess = 0.0
            target.ViewObject.ShapeAppearance = [material]
            report['mesh_authored_material'] = {'SpecularColor': [0.0, 0.0, 0.0], 'Shininess': 0.0}
            target.ViewObject.DisplayMode = 'Shaded'
            unlit = coin.SoLightModel()
            unlit.model = coin.SoLightModel.BASE_COLOR
            unlit.setOverride(True)
            view.getSceneGraph().insertChild(unlit, 0)
            report['mesh_lighting_profile'] = 'BASE_COLOR override; sampler only, no normals/lighting claim'
            expected_nodes = ['SoFCIndexedFaceSet']
            def mutate_consumer():
                target.Mesh = Mesh.createSphere(7 if round_index == 0 else 4, 16)
        else:
            App.ParamGet('User parameter:BaseApp/Preferences/View').SetUnsigned('CbLabelColor', 0xffffffff)
            report['colorbar_authored_text_colors'] = ['0xff0000ff', '0xffffffff']
            source = doc.addObject('Mesh::Feature', 'MeshSource')
            source.Mesh = Mesh.createSphere(5, 16)
            target = doc.addObject('Mesh::Curvature', 'Consumer')
            target.Source = source
            source.ViewObject.Visibility = False
            target.ViewObject.DisplayMode = 'Mean curvature'
            expected_nodes = ['SoFCColorBar', 'SoColorBarLabel']
            def mutate_consumer():
                source.Mesh = Mesh.createSphere(7 if round_index == 0 else 4, 16)
    elif consumer_name == 'fem-mesh':
        import Fem
        import FemGui
        target = doc.addObject('Fem::FemMeshObject', 'Consumer')
        def mesh_at(height):
            mesh = Fem.FemMesh()
            for index, point in enumerate(((-5, -4, 0), (5, -4, 0),
                                           (0, 5, 0), (0, 0, height)), 1):
                mesh.addNode(*point, index)
            mesh.addVolume([1, 2, 3, 4])
            return mesh
        target.FemMesh = mesh_at(6)
        target.ViewObject.DisplayMode = 'Faces, Wireframe & Nodes'
        def mutate_consumer():
            target.FemMesh = mesh_at(10 if round_index == 0 else 3)
    elif consumer_name == 'draft-dimension':
        import Draft
        target = Draft.make_dimension(V(-5, 0, 0), V(5, 0, 0), V(0, 4, 0))
        target.ViewObject.LineColor = (1.0, 1.0, 0.0)
        target.ViewObject.TextColor = (1.0, 1.0, 0.0)
        target.ViewObject.DisplayMode = 'Screen'
        target.ViewObject.FontSize = 24
        target.ViewObject.SelectionStyle = 'BoundBox'
        report['selection_style'] = 'BoundBox'
        expected_nodes = ['SoText2']
        def mutate_consumer():
            target.End = V(9 if round_index == 0 else 3, 0, 0)
    elif consumer_name == 'partdesign-pad':
        import Sketcher
        import PartDesign
        Gui.activateWorkbench('PartDesignWorkbench')
        body = doc.addObject('PartDesign::Body', 'Body')
        source = doc.addObject('Sketcher::SketchObject', 'PadProfile')
        body.addObject(source)
        corners = [V(-5, -4, 0), V(5, -4, 0), V(5, 4, 0), V(-5, 4, 0)]
        for i in range(4):
            source.addGeometry(Part.LineSegment(corners[i], corners[(i+1) % 4]), False)
        target = body.newObject('PartDesign::Pad', 'Consumer')
        target.Profile = source
        target.Length = 6
        source.ViewObject.Visibility = False
        def mutate_consumer():
            target.Length = 10 if round_index == 0 else 3
    elif consumer_name == 'bim-site':
        # These are host dependencies. Do not fake their generated path/text.
        try:
            import ladybug
        except ImportError:
            try:
                import pysolar
            except ImportError:
                report.update(status='UNSUPPORTED', reason='BIM solar diagram requires Ladybug or Pysolar')
                (artifacts / 'result.json').write_text(json.dumps(report, indent=2))
                os.write(1, ('RESULT ' + json.dumps(report) + '\n').encode())
                os._exit(78)
        import Arch
        source = doc.addObject('Part::Feature', 'SiteTerrain')
        source.Shape = Part.makeBox(10, 8, .2, V(-5, -4, 0))
        target = Arch.makeSite(baseobj=source, name='Consumer')
        target.Latitude = -23.55
        target.Longitude = -46.63
        target.TimeZone = -3
        target.ViewObject.SolarDiagramScale = 10
        target.ViewObject.SolarDiagramColor = (1.0, 1.0, 0.0)
        target.ViewObject.SolarDiagram = False
        expected_nodes = ['SoText2']
        def mutate_consumer():
            target.ViewObject.SolarDiagramPosition = V(2 if round_index == 0 else -2, 1, 0)
    else:
        target = doc.addObject('Part::Feature', 'Consumer')
        target.Shape = Part.makeBox(10, 8, 6, V(-5, -4, 0))
        expected_nodes = ['SoTransformDragger']
        edit_consumer = True
        def mutate_consumer():
            target.Shape = Part.makeBox(12 if round_index == 0 else 8, 8, 6, V(-5, -4, 0))
    if source is not None and consumer_name != 'measure-distance':
        source.ViewObject.Visibility = False
    doc.recompute()
    Gui.Selection.clearSelection()
    target.ViewObject.Visibility = True
    if consumer_name == 'bim-site':
        target.ViewObject.SolarDiagram = True
    if consumer_name in ('partdesign-pad', 'fem-mesh', 'transform-dragger', 'mesh-curvature', 'mesh-interactive'):
        view.viewAxonometric()
    else:
        view.viewTop()
    view.fitAll()
    target.ViewObject.Visibility = False
    if consumer_name == 'bim-site':
        target.ViewObject.SolarDiagram = False
    round_index = 0
    move(QtCore.QPoint(15, 15))
    prepare_mesh_ui()
    prepare_edit_ui()
    step(consumer_bare)


def consumer_bare():
    global bare, record, visible_publication_wait
    report['coin_images'] = require_single_coin(Path('/proc/self/maps').read_text())
    bare = capture('consumer-bare-' + str(round_index))
    ratio = viewer_widget().viewport().devicePixelRatioF()
    require_dpr(ratio, float(os.environ.get('QT_SCALE_FACTOR', '1')))
    record = {'resized': bool(round_index), 'dpr': ratio, 'bare_size': [bare.width(),bare.height()]}
    report['stages'].append(record)
    observe_coin_event_state('bare-before-show')
    record['publication_before_show'] = input_observer.publication()
    record['before_show_monotonic_ns'] = time.monotonic_ns()
    if native:
        visible_publication_wait = NativePublicationQuietWindow(record['publication_before_show'])
    target.ViewObject.Visibility = True
    if consumer_name == 'bim-site':
        target.ViewObject.SolarDiagram = True
    if edit_consumer:
        Gui.activeDocument().setEdit(target.Name, 1 if consumer_name == 'transform-dragger' else 0)
        if not Gui.activeDocument().getInEdit():
            raise RuntimeError('consumer failed to enter actual edit mode')
        prepare_edit_ui()
    if native:
        step(await_visible_publication)
    else:
        step(consumer_visible)


def await_visible_publication():
    state = input_observer.publication()
    now_ms = time.monotonic_ns()/1e6
    ready = visible_publication_wait.observe(state, now_ms)
    observation = record.setdefault('publication_wait', {'quiet_ms': 600, 'checks': 0, 'changes': []})
    observation['checks'] += 1
    if not observation['changes'] or observation['changes'][-1]['publication'] != state:
        observation['changes'].append({'monotonic_ms': now_ms, 'publication': state})
    observation.update(latest=state, observed_monotonic_ms=now_ms,
                       quiet_started_monotonic_ms=visible_publication_wait.quiet_started_ms,
                       ready=ready)
    if ready:
        consumer_visible()
    else:
        # This timer only reads publication metadata. The runner's unchanged
        # 120-second process deadline bounds cold preparation and visibility.
        step(await_visible_publication, 50)


def consumer_visible():
    global first, label_nodes, saved_strings
    record['publication_before_capture'] = input_observer.publication()
    record['capture_started_monotonic_ns'] = time.monotonic_ns()
    first = capture('consumer-visible-' + str(round_index))
    record['capture_finished_monotonic_ns'] = time.monotonic_ns()
    record['publication_after_capture'] = input_observer.publication()
    record['visible_size'] = [first.width(),first.height()]
    record['visible_changes'] = difference(bare, first)
    try:
        require_content(record['visible_changes'])
    except RuntimeError as error:
        observe_failed_visibility(error)
        return
    record['nodes'] = {}
    for type_name in expected_nodes:
        nodes = find_nodes(type_name)
        record['nodes'][type_name] = len(nodes)
        if not nodes:
            raise RuntimeError('document consumer omitted actual ' + type_name)
    if consumer_name == 'mesh-interactive':
        step(mesh_begin)
        return
    if consumer_name in LABEL_CONSUMERS:
        label_type = 'SoColorBarLabel' if consumer_name == 'mesh-curvature' else expected_nodes[0]
        label_nodes = find_nodes(label_type)
        saved_strings = [node.getField('string').getValue() if
                         not hasattr(node.getField('string'), 'getNum') else
                         list(node.getField('string').getValues()) for node in label_nodes]
        if not any(str(value).strip("[]' ") for value in saved_strings):
            raise RuntimeError('consumer label has no actual text')
        if consumer_name == 'mesh-curvature':
            # Change the actual producer's text format. Editing derived child
            # strings can be overwritten by a refreshed color-scale snapshot.
            App.ParamGet('User parameter:BaseApp/Preferences/View').SetUnsigned('CbLabelColor', 0xff0000ff)
            step(labels_muted)
            return
        for node in label_nodes:
            field = node.getField('string')
            if hasattr(field, 'setValues'):
                field.setNum(1)
                field.setValues(0, [''])
            else:
                field.setValue('')
        step(labels_muted)
    else:
        step(prepare_input)


def observe_failed_visibility(original_error):
    # This process has already failed. These bounded, read-only observations
    # diagnose delayed screen visibility; they never request another frame,
    # update a widget/scene, retry a gate, or authorize a PASS.
    report.update(status='FAIL', reason=str(original_error))
    started = time.monotonic_ns()
    diagnostics = {'original_failure': str(original_error),
                   'original_visible_changes': record['visible_changes'],
                   'started_monotonic_ns': started,
                   'initial_publication': input_observer.publication(), 'observations': []}
    record['failed_visibility_diagnostics'] = diagnostics
    def observe(delay_ms):
        item = {'scheduled_delay_ms': delay_ms,
                'elapsed_ms': (time.monotonic_ns()-started)/1e6,
                'publication_before_capture': input_observer.publication()}
        try:
            image = capture('consumer-failed-visible-' + str(round_index) + '-' + str(delay_ms) + 'ms')
            item['size'] = [image.width(),image.height()]
            item['changes_from_failed_capture'] = difference(first, image)
            item['changes_from_bare'] = difference(bare, image)
        except Exception as diagnostic_error:
            item['observation_error'] = str(diagnostic_error)
        item['publication_after_capture'] = input_observer.publication()
        item['finished_elapsed_ms'] = (time.monotonic_ns()-started)/1e6
        diagnostics['observations'].append(item)
        if delay_ms == 1000:
            finish(original_error)
    for delay in (50,500,1000):
        QtCore.QTimer.singleShot(delay, lambda delay=delay: observe(delay))


def labels_muted():
    global muted
    muted = capture('consumer-label-muted-' + str(round_index))
    if consumer_name == 'mesh-curvature':
        App.ParamGet('User parameter:BaseApp/Preferences/View').SetUnsigned('CbLabelColor', 0xffffffff)
        step(labels_restored)
        return
    for node, value in zip(label_nodes, saved_strings):
        field = node.getField('string')
        if isinstance(value, list):
            field.setNum(len(value))
            field.setValues(0, value)
        else:
            field.setValue(value)
    step(labels_restored)


def mesh_begin():
    global mesh_camera_before
    mesh_camera_before = view.getCamera()
    move(QtCore.QPoint(15, 15))
    button(True, 2)
    step(mesh_move)


def mesh_move():
    move(QtCore.QPoint(55, 35))
    step(mesh_held)


def mesh_held():
    global mesh_active, mesh_camera_held, mesh_observations
    pressed = bool(QtWidgets.QApplication.mouseButtons() & QtCore.Qt.MiddleButton)
    if not pressed:
        raise RuntimeError('mesh observation occurred after native pointer release')
    mesh_camera_held = view.getCamera()
    mesh_active = capture('consumer-mesh-pointer-held-' + str(round_index))
    mask = np.any(rgb_array(bare) != rgb_array(mesh_active), axis=2)
    facets = list(target.Mesh.Facets)
    limit = 10
    stride = len(facets) // limit + 1
    projected, hits = 0, 0
    vertices = []
    viewport = viewer_widget().viewport()
    ratio = viewport.devicePixelRatioF()
    visible_widgets = [widget for widget in QtWidgets.QApplication.allWidgets()
                       if isValid(widget) and widget.isVisible() and widget is not viewport and
                       not widget.isAncestorOf(viewport)]
    record['mesh_visible_widgets'] = [widget_description(widget) for widget in visible_widgets]
    for index in range(0, len(facets), stride):
        points = facets[index].Points
        for vertex, point in enumerate(points):
            x, y = view.getPointOnScreen(App.Vector(point))
            x, y = round(x), mesh_active.height()-1-round(y)
            if 0 <= x < mesh_active.width() and 0 <= y < mesh_active.height():
                projected += 1
                found = bool(np.any(mask[max(0,y-2):y+3, max(0,x-2):x+3]))
                hits += int(found)
                global_point = viewport.mapToGlobal(QtCore.QPoint(round(x/ratio),round(y/ratio)))
                overlays = [widget_description(widget) for widget in visible_widgets
                            if isValid(widget) and widget.rect().contains(widget.mapFromGlobal(global_point))]
                vertices.append({'facet': index, 'vertex': vertex, 'pixel': [x,y], 'present': found,
                                 'widget_at': widget_description(QtWidgets.QApplication.widgetAt(global_point)),
                                 'graphics_item_at': graphics_item_description(viewer_widget().itemAt(
                                     QtCore.QPoint(round(x/ratio),round(y/ratio)))),
                                 'ui_overlaps': overlays})
    mesh_observations = dict(facets=len(facets), limit=limit, pressed=pressed,
                             camera_changed=mesh_camera_before != mesh_camera_held,
                             active_pixels=int(np.count_nonzero(mask)),
                             projected_samples=projected, sample_hits=hits)
    record['interactive_sample_vertices'] = vertices
    button(False, 2)
    step(mesh_released)


def mesh_released():
    global first
    if QtWidgets.QApplication.mouseButtons() & QtCore.Qt.MiddleButton:
        raise RuntimeError('mesh native pointer was not released')
    if view.getCamera() != mesh_camera_held:
        raise RuntimeError('mesh active/released observations used different cameras')
    first = capture('consumer-mesh-pointer-released-' + str(round_index))
    mesh_observations['released_pixels'] = difference(bare, first)
    record['interactive_mesh'] = mesh_observations
    require_interactive_mesh(**mesh_observations)
    require_mutation(difference(mesh_active, first))
    step(before_mutation)


def labels_restored():
    global first
    first = capture('consumer-label-restored-' + str(round_index))
    a, b = rgb_array(muted), rgb_array(first)
    changed = np.any(a != b, axis=2)
    if consumer_name == 'mesh-curvature':
        # Only the public producer text color changes, red -> white. The
        # gradient/range/geometry remain fixed and cannot replace glyph pixels.
        red = (a[:,:,0]>180) & (a[:,:,1]<100) & (a[:,:,2]<100)
        white = np.all(b>180, axis=2)
        glyphs = int(np.count_nonzero(changed & red & white))
        record['glyph_oracle'] = 'producer CbLabelColor red/white glyph mask'
    else:
        # Frame/datum labels can own backgrounds: count bright strokes where
        # text removal changed pixels, rather than their dark rectangles.
        glyphs = int(np.count_nonzero(changed & (np.max(b, axis=2) > 180)))
        record['glyph_oracle'] = 'bright strokes in actual string removal mask'
    record['glyph_pixels'] = glyphs
    require_content(record['visible_changes'], glyphs)
    step(prepare_input)


def identity(point):
    viewport = viewer_widget().viewport()
    ratio = viewport.devicePixelRatioF()
    pos = (round(point.x()*ratio), round((viewport.height()-1-point.y())*ratio))
    if consumer_name == 'sketcher-datum':
        import SketcherGui
        info = SketcherGui.getActiveSketchPreselection(pos)
        if info and info.get('ObjectName') == target.Name:
            names = info.get('SubElementNames') or []
            if names and names[0] == 'Constraint1':
                return target.Name, names[0]
        return None
    info = view.getObjectInfo(pos)
    owners = {target.Name}
    if consumer_name == 'mesh-curvature':
        # Curvature consumes the source's highlight node. FreeCAD can report
        # that source or its owning curvature occurrence, both in this fixture.
        owners.add(source.Name)
    if info and info.get('Object') in owners:
        if consumer_name == 'mesh-curvature':
            # The legacy SoFCSelection highlight node calls its presentation
            # "Main". Resolve the nearest geometric pick through the public
            # provider, which defines the selectable element independently of
            # preselection or the later click (whole object for Curvature).
            root = coin.SoSeparator()
            root.addChild(view.getCameraNode())
            root.addChild(view.getSceneGraph())
            picker = coin.SoRayPickAction(coin.SbViewportRegion(
                round(viewport.width()*ratio), round(viewport.height()*ratio)))
            picker.setPoint(coin.SbVec2s(*pos))
            picker.setPickAll(False)
            picker.apply(root)
            picked = picker.getPickedPoint()
            if picked is None:
                return None
            element = target.ViewObject.getElementPicked(picked)
            record['independent_pointer_raw'] = (info['Object'], info.get('Component', ''))
            record['provider_pick_element'] = element
            if element is None:
                return None
            return info['Object'], element
        # getObjectInfo resolves a Body/Link to its leaf, whereas GUI selection
        # retains the parent occurrence. Compare the complete logical identity.
        if info.get('ParentObject') is not None:
            return canonical_identity((info['ParentObject'].Name, info['SubName']))
        return canonical_identity((info['Object'], info.get('Component', '')))
    return None


def canonical_identity(value):
    return canonical_topology_identity(doc, value) if consumer_name == 'partdesign-pad' else value


def prepare_input():
    global input_point, expected_identity, drag_before, drag_node, event_start, drag_probe, drag_destination, qt_event_start
    active()
    event_start = len(motion_events), len(button_events)
    qt_event_start = dict(input_observer.events)
    if consumer_name == 'transform-dragger':
        drag_node = find_nodes('SoTransformDragger')[0]
        drag_before = tuple(target.Placement.Base)
        root = coin.SoSeparator()
        root.addChild(view.getCameraNode())
        root.addChild(view.getSceneGraph())
        mask = np.any(rgb_array(bare) != rgb_array(first), axis=2)
        ys, xs = np.nonzero(mask)
        ratio = viewer_widget().viewport().devicePixelRatioF()
        input_point = None
        translators = [drag_node.getPart(name, False) for name in
                       ('xTranslatorDragger', 'yTranslatorDragger', 'zTranslatorDragger')]
        if not all(translators):
            raise RuntimeError('actual transform consumer has no translation handles')
        drag_probe = host_helper.host_consumer_drag_probe_create(int(drag_node.this))
        if not drag_probe:
            raise RuntimeError('test helper could not attach to the real dragger')
        for index in np.linspace(0, len(xs)-1, min(256, len(xs)), dtype=int):
            picker = coin.SoRayPickAction(coin.SbViewportRegion(first.width(), first.height()))
            picker.setPoint(coin.SbVec2s(int(xs[index]), int(first.height()-1-ys[index])))
            picker.setPickAll(False)
            picker.apply(root)
            hit = picker.getPickedPoint()
            if hit is not None:
                path = hit.getPath()
                if path.containsNode(drag_node) and any(path.containsNode(node) for node in translators):
                    input_point = QtCore.QPoint(round(xs[index]/ratio), round(ys[index]/ratio))
                    axis = next(i for i,node in enumerate(translators) if path.containsNode(node))
                    vectors = (App.Vector(1,0,0), App.Vector(0,1,0), App.Vector(0,0,1))
                    a = view.getPointOnScreen(target.Placement.Base)
                    b = view.getPointOnScreen(target.Placement.Base + vectors[axis])
                    dx,dy = (b[0]-a[0])/ratio, -(b[1]-a[1])/ratio
                    length = (dx*dx + dy*dy)**.5
                    if not length:
                        raise RuntimeError('picked translation axis has no screen projection')
                    delta = QtCore.QPoint(round(80*dx/length), round(80*dy/length))
                    drag_destination = input_point + delta
                    if not viewer_widget().viewport().rect().contains(drag_destination):
                        drag_destination = input_point - delta
                    if not viewer_widget().viewport().rect().contains(drag_destination):
                        raise RuntimeError('translation handle has no in-viewport drag destination')
                    record['drag_axis'] = axis
                    record['drag_pointer_start'] = [input_point.x(), input_point.y()]
                    record['drag_pointer_end'] = [drag_destination.x(), drag_destination.y()]
                    record['nearest_dragger_path'] = [str(path.getNode(i).getTypeId().getName())
                                                      for i in range(path.getLength())]
            if input_point is not None:
                break
        if input_point is None:
            raise RuntimeError('no visible translation handle with an actual dragger path')
        record['picked_translation_handle'] = True
    else:
        mask = np.any(rgb_array(bare) != rgb_array(first), axis=2)
        ys, xs = np.nonzero(mask)
        ratio = viewer_widget().viewport().devicePixelRatioF()
        input_point, expected_identity = None, None
        for index in np.linspace(0, len(xs)-1, min(512, len(xs)), dtype=int):
            point = QtCore.QPoint(round(xs[index]/ratio), round(ys[index]/ratio))
            hit = identity(point)
            if consumer_name == 'bim-site' and hit and hit[1] != '':
                # Exercise the authored SolarDiagram itself. Terrain EdgeN
                # selection has a different visual policy in the real host.
                continue
            if consumer_name == 'measure-distance' and hit and not all(
                    identity(point + QtCore.QPoint(dx,dy)) == hit
                    for dx,dy in ((-8,0),(8,0),(0,-8),(0,8))):
                # The frame label has a real pickable interior. Choose that
                # interior, not an antialiased boundary merely within the
                # viewer's pick radius, after each authored distance/resize.
                continue
            if consumer_name in ('fem-mesh', 'partdesign-pad') and hit and (
                    not (hit[1].startswith('Elem') if consumer_name == 'fem-mesh' else
                         re.search(r'(?:^|\.)Face[0-9]+$', hit[1])) or not all(
                        identity(point + QtCore.QPoint(dx,dy)) == hit
                        for dx,dy in ((-8,0),(8,0),(0,-8),(0,8)))):
                continue
            if hit:
                input_point, expected_identity = point, hit
                break
        if input_point is None:
            raise RuntimeError('no independently picked consumer content for native input')
        record['expected_pointer'] = expected_identity
        if consumer_name == 'measure-distance':
            record['pointer_pick_neighborhood'] = [
                {'offset': [dx,dy], 'identity': identity(input_point + QtCore.QPoint(dx,dy))}
                for dx,dy in ((0,0),(-8,0),(8,0),(0,-8),(0,8))]
    viewport = viewer_widget().viewport()
    record['pointer_fixture'] = {'logical_position': [input_point.x(),input_point.y()],
                                 'viewport_size': [viewport.width(),viewport.height()],
                                 'dpr': viewport.devicePixelRatioF()}
    record['pointer_ui_before_motion'] = pointer_ui_state(input_point)
    observe_coin_event_state('before-pointer-motion')
    move(input_point)
    step(consumer_hover)


def consumer_hover():
    observe_coin_event_state('after-pointer-motion')
    pointer = viewer_widget().viewport().mapFromGlobal(QtGui.QCursor.pos())
    record['pointer_observed'] = [pointer.x(),pointer.y()]
    record['qt_last_motion'] = input_observer.last_motion
    record['pointer_ui_after_motion'] = pointer_ui_state(pointer)
    record['qt_hover_events'] = {key: count-qt_event_start[key]
                                 for key,count in input_observer.events.items()}
    record['qt_filter_seen'] = dict(input_observer.seen)
    record['qt_filter_rejected'] = dict(input_observer.rejected)
    record['qt_filter_observations'] = list(input_observer.filter_observations)
    record['coin_last_motion'] = (list(motion_events[-1].get('Position', []))
                                   if motion_events else None)
    if pointer != input_point:
        raise RuntimeError('native pointer did not reach consumer')
    if consumer_name != 'transform-dragger':
        require_pointer_identity(identity(pointer), expected_identity)
        pre = Gui.Selection.getPreselection()
        names = list(pre.SubElementNames)
        actual = (pre.ObjectName, names[0] if names else '')
        record['observed_preselection_raw'] = actual
        actual = canonical_identity(actual)
        record['observed_preselection'] = actual
        require_pointer_identity(actual, expected_identity)
        record['hover_changes'] = difference(first, capture('consumer-hover-' + str(round_index)))
        # These actual CoinGL consumers update preselection without a 3D hover
        # highlight. Preserve that behavior; do not invent a host feature.
        record['visual_hover_provided_by_host'] = consumer_name not in (
            'measure-distance', 'draft-dimension', 'fem-mesh', 'bim-site')
        require_host_hover(record['hover_changes'], record['visual_hover_provided_by_host'])
    record['motion_events_before_click'] = len(motion_events)
    observe_coin_event_state('before-pointer-click')
    button(True)
    if consumer_name == 'transform-dragger':
        step(drag_move)
    else:
        button(False)
        step(consumer_clicked)


def drag_move():
    move(drag_destination)
    step(drag_release)


def drag_release():
    button(False)
    step(consumer_clicked)


def consumer_clicked():
    global drag_probe
    observe_coin_event_state('after-pointer-click')
    qt_events = {key: count-qt_event_start[key] for key,count in input_observer.events.items()}
    record['qt_input_events'] = qt_events
    record['qt_filter_seen'] = dict(input_observer.seen)
    record['qt_filter_rejected'] = dict(input_observer.rejected)
    record['qt_filter_observations'] = list(input_observer.filter_observations)
    record['coin_input_events'] = {'motion': len(motion_events)-event_start[0],
                                   'buttons': len(button_events)-event_start[1]}
    if qt_events['press'] < 1 or qt_events['release'] < 1 or qt_events['motion'] < 1:
        raise RuntimeError('consumer did not receive native Qt input events')
    if consumer_name == 'transform-dragger':
        after = tuple(target.Placement.Base)
        drag_events = {phase: int(host_helper.host_consumer_drag_probe_count(drag_probe,index))
                       for index,phase in enumerate(('start','motion','finish'))}
        record['dragger_callbacks'] = drag_events
        record.update(drag_before=drag_before, drag_after=after,
                      button_events=qt_events['press']+qt_events['release'],
                      motion_events=qt_events['motion'],
                      drag_node_translation=tuple(drag_node.getField('translation').getValue()))
        require_drag(drag_before, after, record['motion_events'], record['button_events'], drag_events)
        host_helper.host_consumer_drag_probe_destroy(drag_probe)
        drag_probe = None
    else:
        # NoResolve preserves the Body/Link occurrence used by preselection and
        # getObjectInfo's ParentObject/SubName; the default resolves to a leaf.
        selection = Gui.Selection.getSelectionEx(doc.Name, 0)
        raw = [(item.ObjectName, sub) for item in selection
                  for sub in (list(item.SubElementNames) or [''])]
        record['observed_selection_raw'] = raw
        actual = [canonical_identity(value) for value in raw]
        record['observed_selection'] = actual
        if expected_identity not in actual:
            raise RuntimeError('native click did not select independently picked consumer')
        record['clicked'] = actual
    observe_coin_event_state('before-move-off-consumer')
    move(QtCore.QPoint(15, 15))
    observe_coin_event_state('after-move-off-request')
    step(selection_visible)


def selection_visible():
    global first
    observe_coin_event_state('after-move-off-settled')
    if consumer_name != 'transform-dragger':
        selected = capture('consumer-selected-' + str(round_index))
        record['selection_changes'] = difference(first, selected)
        record['visual_selection_provided_by_host'] = consumer_name not in (
            'measure-distance', 'fem-mesh')
        require_host_selection(record['selection_changes'], record['visual_selection_provided_by_host'])
    else:
        # Keep the actual authored drag. Clearing selection must preserve this
        # result, and the subsequent geometry edit starts from the dragged state.
        first = capture('consumer-dragged-' + str(round_index))
    observe_coin_event_state('before-clear-selection')
    Gui.Selection.clearSelection()
    observe_coin_event_state('after-clear-selection')
    step(before_mutation)


def before_mutation():
    global mutation_baseline
    observe_coin_event_state('before-authored-edit')
    mutation_baseline = capture('consumer-before-update-' + str(round_index))
    require_cleanup(difference(first, mutation_baseline))
    mutate_consumer()
    doc.recompute()
    observe_coin_event_state('after-authored-edit')
    if consumer_name == 'mesh-curvature':
        bounds = (-1.0, 1.0, 2) if round_index == 0 else (-2.0, 2.0, 1)
        bars = find_nodes('SoFCColorBar')
        if not bars:
            raise RuntimeError('no actual colorbar for public range authoring')
        for bar in bars:
            if not host_helper.host_consumer_colorbar_set_range(int(bar.this), *bounds):
                raise RuntimeError('public host colorbar range authoring failed')
        record['authored_colorbar_range'] = list(bounds)
    step(consumer_mutated)


def consumer_mutated():
    image = capture('consumer-updated-' + str(round_index))
    record['mutation_changes'] = difference(mutation_baseline, image)
    require_mutation(record['mutation_changes'])
    if consumer_name in LABEL_CONSUMERS:
        label_type = 'SoColorBarLabel' if consumer_name == 'mesh-curvature' else expected_nodes[0]
        current_strings = []
        for node in find_nodes(label_type):
            field = node.getField('string')
            current_strings.append(list(field.getValues()) if hasattr(field, 'getNum')
                                   else field.getValue())
        record['labels_before_update'] = saved_strings
        record['labels_after_update'] = current_strings
        if consumer_name != 'bim-site' and saved_strings == current_strings:
            raise RuntimeError('consumer changed geometry but did not regenerate its labels')
    if edit_consumer:
        Gui.activeDocument().resetEdit()
    observe_coin_event_state('before-consumer-hide')
    target.ViewObject.Visibility = False
    if consumer_name == 'bim-site':
        target.ViewObject.SolarDiagram = False
    # The mutation also changes a measurement source. Hide it in both images
    # before the removal oracle so changed model geometry cannot count as residue.
    if source is not None and consumer_name != 'measure-distance':
        source.ViewObject.Visibility = False
    doc.recompute()
    observe_coin_event_state('after-consumer-hide')
    step(consumer_removed)


def consumer_removed():
    global round_index
    observe_coin_event_state('consumer-removed-settled')
    image = capture('consumer-removed-' + str(round_index))
    record['removed_size'] = [image.width(),image.height()]
    # Measurement source is hidden from the initial baseline as well.
    record['remaining_changes'] = difference(bare, image)
    require_cleanup(record['remaining_changes'])
    if not round_index:
        round_index = 1
        observe_coin_event_state('before-window-resize')
        Gui.getMainWindow().resize(1000, 700)
        observe_coin_event_state('after-window-resize')
        prepare_mesh_ui()
        prepare_edit_ui()
        step(consumer_bare)
    else:
        doc.removeObject(target.Name)
        doc.recompute()
        step(consumer_idle_baseline)


def consumer_idle_baseline():
    report['idle_start'] = int(viewer_widget().property('wgpuFrameCount') or 0)
    step(consumer_idle, 1200)


def consumer_idle():
    report['idle_end'] = int(viewer_widget().property('wgpuFrameCount') or 0)
    if native:
        require_idle(report['idle_start'], report['idle_end'])
    finish()
