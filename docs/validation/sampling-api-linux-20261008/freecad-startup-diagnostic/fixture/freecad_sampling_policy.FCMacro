# Real FreeCAD viewer and screen-content contracts, with explicit per-view policy.
from pathlib import Path
import os
exec((Path(os.environ['COIN_TEST_MACRO_DIR']) / 'freecad_screen_content.FCMacro').read_text())
report['test'] = 'freecad-sampling-policy'
policy = int(os.environ.get('COIN_TEST_PORTABLE_SAMPLING', '1'))
report['sampling_policy'] = policy
original_axes_baseline = axes_baseline
original_capture = capture

# This automated content fixture drives camera and picking through the API.
# Discard interactive input in this private host process so a cursor gesture or
# toolbar shortcut cannot mutate its camera/document between screen captures.
class SamplingFixtureInputGuard(QtCore.QObject):
    blocked = {QtCore.QEvent.MouseButtonPress, QtCore.QEvent.MouseButtonRelease,
               QtCore.QEvent.MouseButtonDblClick, QtCore.QEvent.MouseMove,
               QtCore.QEvent.Wheel, QtCore.QEvent.KeyPress, QtCore.QEvent.KeyRelease,
               QtCore.QEvent.ContextMenu, QtCore.QEvent.TouchBegin,
               QtCore.QEvent.TouchUpdate, QtCore.QEvent.TouchEnd,
               QtCore.QEvent.NativeGesture}
    def eventFilter(self, obj, event):
        if event.type() in self.blocked:
            report['interactive_input_blocked'] = report.get('interactive_input_blocked', 0) + 1
            return True
        return False

sampling_input_guard = SamplingFixtureInputGuard()
QtWidgets.QApplication.instance().installEventFilter(sampling_input_guard)
report['fixture_interactive_input'] = 'blocked in this host process'

def axes_baseline():
    widget = viewer_widget()
    main = Gui.getMainWindow()
    # EWMH changes stacking without recreating Qt's native surface.
    import subprocess
    subprocess.run(['wmctrl', '-i', '-r', hex(int(main.winId())), '-b',
                    'add,above'], check=True, timeout=3)
    loop = QtCore.QEventLoop()
    QtCore.QTimer.singleShot(60, loop.quit)
    loop.exec()
    state = subprocess.check_output(['xprop', '-id', hex(int(main.winId())),
                                     '_NET_WM_STATE'], timeout=3).decode()
    if '_NET_WM_STATE_ABOVE' not in state:
        raise RuntimeError('window manager did not admit ABOVE for the test host')
    report['fixture_window_state'] = state.strip()
    main.raise_()
    main.activateWindow()
    report['fixture_window_stays_on_top'] = True
    widget.setFocus()
    widget.setProperty('coinRenderPortableSampling', bool(policy))
    # Establish the same top camera before adapter recreation's first baseline.
    # These explicit host redraws do not relax any image/change/removal gate.
    view.viewTop()
    for _ in range(2):
        view.redraw()
        Gui.updateGui()
    report['prebaseline_redraws'] = 2
    original_axes_baseline()
    # Exercise filter=2 in the real host as well as legacy raster content:
    # a 256-square texture on this small face reaches mip minification at DPR1
    # and under the existing projective mutation at DPR2.
    for name, switch, node, anchor in stages:
        if name != 'projective-uv':
            continue
        group = switch.getChild(0)
        pattern = bytes(channel for y in range(256) for x in range(256)
                        for channel in ((255,255,0,255) if ((x//16+y//16)%2)
                                        else (0,128,255,255)))
        for index in range(group.getNumChildren()):
            child = group.getChild(index)
            if child.isOfType(coin.SoTexture2.getClassTypeId()):
                child.image.setValue(coin.SbVec2s(256,256),4,pattern)
            if child.isOfType(coin.SoComplexity.getClassTypeId()):
                child.textureQuality = .5
        report['projective_sampling_fixture'] = {'dimensions':[256,256],
            'quality':.5,'filter':'NEAREST_MIPMAP_LINEAR','unit':0}

def capture(name):
    widget = viewer_widget()
    Gui.getMainWindow().raise_()
    # Dismiss only this test host's menus/tooltips, which otherwise occlude
    # screen pixels and invalidate comparison with its bare viewport.
    popup = QtWidgets.QApplication.activePopupWidget()
    if popup is not None:
        popup.close()
        report['dismissed_popups'] = report.get('dismissed_popups', 0) + 1
    QtWidgets.QToolTip.hideText()
    # A synchronous host redraw establishes the current scene before reading
    # screen pixels; GL presentation can otherwise expose the preceding frame.
    view.redraw()
    Gui.updateGui()
    active = widget.property('coinRenderActiveSamplingPolicy')
    if native and (active is None or int(active) != policy):
        raise RuntimeError('explicit sampling policy was not admitted by the real host')
    report['active_sampling_policy'] = int(active) if active is not None else None
    # Qt redraw return does not fence the desktop compositor. Require two
    # identical screen reads after event processing, with a bounded deadline.
    # This waits for presentation; it does not change any image/removal gate.
    deadline = time.monotonic() + 0.5
    previous = None
    attempt = 0
    while time.monotonic() < deadline:
        loop = QtCore.QEventLoop()
        QtCore.QTimer.singleShot(60, loop.quit)
        loop.exec()
        image = original_capture(name)
        attempt += 1
        if previous is not None and image == previous:
            report.setdefault('presentation_reads', {})[name] = attempt
            return image
        if previous is not None:
            previous.save(str(artifacts / (name + '-presentation-' + str(attempt-1) + '.png')))
        previous = image
    raise RuntimeError('screen presentation did not settle within 0.5s: ' + name)

# Bound queued cleanup work before measuring idle. The final 1.2s idle gate
# remains exact; a perpetual frame loop never reaches this baseline.
import time
idle_deadline = None
idle_last = None
idle_stable_since = None
original_idle_baseline = content_idle_baseline

def content_idle_baseline():
    global idle_deadline, idle_last, idle_stable_since
    now = time.monotonic()
    count = int(viewer_widget().property('wgpuFrameCount') or 0)
    if idle_deadline is None:
        idle_deadline = now + 5.0
        idle_last = count
        idle_stable_since = now
    if count != idle_last:
        idle_last = count
        idle_stable_since = now
    if now - idle_stable_since >= 0.6:
        report['idle_cleanup_settle_s'] = 5.0 - (idle_deadline-now)
        original_idle_baseline()
    elif now >= idle_deadline:
        raise RuntimeError('cleanup did not settle within 5s')
    else:
        step(content_idle_baseline, 100)

original_baseline_ready = baseline_ready

def baseline_ready():
    # Diagnostic only: isolate root changes caused by picking/font first use.
    before = capture('startup-before-pick')
    viewport = viewer_widget().viewport()
    ratio = viewer_widget().devicePixelRatioF()
    picked = view.getObjectInfo((int(viewport.width()*ratio/2),int(viewport.height()*ratio/2)))
    after_pick = capture('startup-after-pick')
    stages[0][1].whichChild = coin.SO_SWITCH_ALL
    capture('startup-first-glyph')
    stages[0][1].whichChild = coin.SO_SWITCH_NONE
    after_glyph = capture('startup-after-glyph')
    rect = QtCore.QRect(0,0,before.width()-1,before.height()-1)
    report['startup_diagnostic'] = {'picking_delta':changes(before,after_pick,rect),
        'glyph_delta':changes(after_pick,after_glyph,rect),'document_pick':bool(picked)}
    original_baseline_ready()
